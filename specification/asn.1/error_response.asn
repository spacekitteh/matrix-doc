Module-errors DEFINITIONS AUTOMATIC TAGS ::=
BEGIN

Error ::= SEQUENCE {
  errcode ErrorCode,
  error UTF8String }

-- TODO: Convert to a "standard errors" "authentication errors" etc CHOICE
ErrorCode ::= ENUMERATED { M_FORBIDDEN,
  M_UNKNOWN_TOKEN,
  M_BAD_JSON,
  M_NOT_JSON,
  M_NOT_FOUND,
  M_LIMIT_EXCEEDED,
  M_USER_IN_USE,
  M_INVALID_USERNAME,
  M_ROOM_IN_USE,
  M_BAD_PAGINATION,
  M_THREEPID_IN_USE,
  M_THREEPID_NT_FOUND,
  M_SERVER_NT_TRUSTED,
  ... }

END
