Module-Identifiers DEFINITIONS AUTOMATIC TAGS ::=
BEGIN
IMPORTS
  Host, Port FROM Module-URI
ServerName ::= SET { hostname Host,
                           port Port OPTIONAL }
Identifier ::= SET { sigil IdentifierType, 
                          localpart LocalPart, 
                          domain ServerName } 

LocalPart ::= IA5String( FROM ("a".."z" | "0".."9" | "._-="))
 
IdentifierType ::= ENUMERATED { user-id, room, event, room-alias }

UserIdentifier ::= Identifier WITH COMPONENTS ( ..., sigil (user-id))

RoomIdentifier ::= Identifier WITH COMPONENTS ( ..., sigil (room))

EventIdentifier ::= Identifier WITH COMPONENTS ( ..., sigil (event))

RoomAliasIdentifier ::= Identifier WITH COMPONENTS ( ..., sigil (room-alias))

-- TODO: Add "this set must be less than <xyz> bytes when viewed as a string"

END
