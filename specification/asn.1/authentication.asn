Authentication-types DEFINITIONS AUTOMATIC TAGS ::=
BEGIN
IMPORTS Session FROM User-types;
Login-type ::= ENUMERATED { --TODO: Find out how to format these properly for JSON
  password,
  recaptcha,
  oauth2,
  email-identity,
  raw-token,
  pkcs-11,
  openid,
  dummy, 
...}




END

Protocol-user-authentication DEFINITIONS AUTOMATIC TAGS ::=
BEGIN
IMPORTS 
 Session FROM User-Types 
 Login-type FROM Authentication-types;

Flows ::= SET OF (SEQUENCE OF Stage (SIZE 1..MAX)) SIZE(1..MAX)
Stage ::= Login-type
END
